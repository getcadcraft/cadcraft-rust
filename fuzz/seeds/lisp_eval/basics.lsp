(defun f (n) (if (< n 1) 0 (+ n (f (1- n)))))
(setq l (mapcar '1+ '(1 2 3)) s (strcat "a" (itoa (f 10))))
(vl-sort '(3 1 2) '<)
(vl-catch-all-apply '/ '(1 0))
(defun *error* (m) (princ m))
(foreach x l (princ x))
(wcmatch "LINE" "L*,[a-z]#")
(rtos 1.5 4 3) (angtos 1.0 4 2)
(setq sa (vlax-make-safearray 5 '(0 . 2))) (vlax-safearray-fill sa '(1 2 3))
(read "(a . b)") (car 1)
