(setq e (entnext)) (while e (entget e) (setq e (entnext e)))
(entmake '((0 . "LINE") (10 0 0) (11 1 1)))
(entmod (subst '(8 . "N") (assoc 8 (entget (entlast))) (entget (entlast))))
(setq s (ssget "X" '((0 . "LINE,CIRCLE"))))
(command "LINE" '(0 0) '(5 5) "")
(command "CIRCLE" PAUSE 1)
(setq ms (vla-get-modelspace (vla-get-activedocument (vlax-get-acad-object))))
(vlax-for o ms (vla-get-objectname o))
(vla-addline ms (vlax-3d-point 0 0) (vlax-3d-point 1 1))
(getpoint "p") (getkword "k")
(defun c:T1 () (princ "t"))
